MiscImplicitDefinitions
  { iso(1) identified-organization(3) amazon(187) misc(900) implicit-attributes(2) }

DEFINITIONS IMPLICIT TAGS ::=
BEGIN

IMPORTS

  DirectoryString
       FROM PKIX1Explicit88 {iso(1) identified-organization(3) dod(6)
       internet(1) security(5) mechanisms(5) pkix(7) id-mod(0)
       id-pkix1-explicit(18)};


	-- From RFC 2985
   PKCS9String ::= CHOICE {
           ia5String IA5String (SIZE(1..MAX)),
           directoryString DirectoryString
   }

	-- From RFC 7633
       Features ::= SEQUENCE OF INTEGER

END
