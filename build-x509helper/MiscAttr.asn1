MiscAttributeForDistinguishedNames
  { iso(1) identified-organization(3) amazon(187) misc(900) name-attributes(1) }

DEFINITIONS EXPLICIT TAGS ::=
BEGIN

IMPORTS

  DirectoryString
       FROM PKIX1Explicit88 {iso(1) identified-organization(3) dod(6)
       internet(1) security(5) mechanisms(5) pkix(7) id-mod(0)
       id-pkix1-explicit(18)};

PostalAddress ::= SEQUENCE SIZE (1..MAX) OF DirectoryString

END
